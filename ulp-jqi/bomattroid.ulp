#require 6.0000




/*****************************************************************************
This is a ULP script for the CADSOFT EAGLE PCB editor.

bomattroid-20131004 ULP combines "bom_with_attributes_v1.06" (by CADSOFT)
with centroid location logic and a few helper functions taken from
"bom-am-19" (by Robert A. Rioja) to generate a Bill of Materials BoM
plus centroid data (i.e., X-Y locations of components on board)
for pick-and-place.

http://milbert.com/sw/eagle
mike@milbert.com
2013-10-03


-----
Notes
The "centroid" X-Y location of each component is simply its origin (0,0).
Centroid data is available only in "by part" view (not "by value").


---------------------------
bomattroid revision history


2013-10-04
- Added escapeDoubleQuotes() to double-double-quote all double-quotes, per CSV spec.
- Adapted MakeListCSV() to call escapeDoubleQuotes().


2013-10-03
- Fork from bom_with_attributes_v1.06
- Add centroid location logic and several helper functions from bom-am-19




------------------------------------------
bom_with_attributes_v1.06 revision history


1.06 2012-08-17 cwi
- CSV output with ";" or "," as separator.
- Library of a part will be listed, too. (Ricardo Monleone)
- Corrected GenerateValueList() function according to suggestions of Jonas Meyer


1.05
- 2012-03-01 alf@cadsoft.de:
  Change PartValue[], PartDevice[], PartPackage[], PartHeadline[], PartDescription[] to normal
  string. Numeric strings with only numerical characters, sorts up to 8 characters!


1.04
- List also Packages by Value


1.03
- Added missing description column in value mode.


1.02
- CSV export added after a suggestion of Christian Schlittler
- File extension for text file output changed from .bom to .txt


1.01
- Dialog mask for text or html output selection corrected


1.00
- Initial release

*/




#usage "en: <b>Export a Bill Of Material</b>\n"
           "<p>"
           "Generates a project's <i>Bill Of Material</i>&nbsp;&nbsp;including the attributes "
           "introduced in version 5.0.0."
           "<p>"
           "<author>Author: support@cadsoft.de</author><br>"
           "<author>Modified to use the new attributes by Carsten Wille.</author><br>",
       "de: <b>Stückliste exportieren</b>\n"
           "<p>"
           "Erzeugt die <i>Stückliste</i> (Bill Of Material) eines Projekts, einschließlich der"
           " mit Version 5.0.0 neu eingeführten Attribute."
           "<p>"
           "<author>Autor: support@cadsoft.de</author><br>"
           "<author>Modifiziert von Carsten Wille, um die neuen Attribute zu nutzen.</author><br>"




// THIS PROGRAM IS PROVIDED AS IS AND WITHOUT WARRANTY OF ANY KIND, EXPRESSED OR IMPLIED




string HelpTextEN =
  "<b>How to generate the Bill Of Material</b>\n"
  "<p>\n"
  "<b>List type</b>\n"
  "<p>\n"
  "The <i>Bill Of Material</i> can be generated either as a list\n"
  "of parts (where every part is listed on a line of its own),\n"
  "or as a list of values, where all parts with the same value are grouped\n"
  "together in one line. Use the <b><u>P</u>arts</b> and <b><u>V</u>alues</b>\n"
  "radio buttons to select the list type.\n"
  "<p>\n"
  "<b>Output format</b>\n"
  "<p>\n"
  "Choose between pure ASCII <b><u>T</u>ext</b> format, <b><u>C</u>SV</b> or <b><u>H</u>TML</b>.\n"
  ;




string HelpTextDE =
  "<b>Erzeugen der Stückliste</b>\n"
  "<p>\n"
  "<b>Listen-Typ</b>\n"
  "<p>\n"
  "Die <i>Stückliste</i> kann entweder als Liste der Bauteile generiert werden\n"
  "(wobei jedes Bauteil in einer eigenen Zeile aufgeführt wird),\n"
  "oder als Liste der Werte, wobei alle Bauteile mit dem gleichen Wert in einer Zeile\n"
  "zusammengefasst werden. Mit den Radio-Buttons <b><u>B</u>auteile</b> und <b><u>W</u>erte</b>\n"
  "kann zwischen den beiden Listen-Typen gewählt werden.\n"
  "<p>\n"
  "<b>Ausgabeformat</b>\n"
  "<p>\n"
  "Wählen Sie zwischen reinem ASCII-<b><u>T</u>ext</b>, <b><u>C</u>SV</b> oder <b><u>H</u>TML</b>"
  "-Format.\n"
  ;




string I18N[] = {
  "en\v"
  "de\v"
  ,
  "<hr><b>ERROR: No schematic!</b><p>\nThis program can only work in the schematic editor.\v"
  "<hr><b>FEHLER: Kein Schaltplan!</b><p>\nDieses Programm kann nur in einem Schaltplan verwendet"
  " werden.\v"
  ,
  "Part\tValue\tDevice\tPackage\tDescription\v"
  "Bauteil\tWert\tDevice\tPackage\tDescription\v"
  ,
  "Qty\tValue\tDevice\tPackage\tParts\v"      // 2011-04-08
  "Menge\tWert\tDevice\tGehäuse\tBauteile\v"  // 2011-04-08
  ,
  "Partlist exported from %s at %s\v"
  "Stückliste exportiert aus %s am %s\v"
  ,
  "Bill Of Material - Preview\v"
  "Stückliste - Vorschau\v"
  ,
  "-Close\v"
  "-Schließen\v"
  ,
  "Save Bill Of Material\v"
  "Stückliste speichern\v"
  ,
  "File '\v"
  "Datei '\v"
  ,
  "' exists\n\nOverwrite?\v"
  "' existiert\n\nÜberschreiben?\v"
  ,
  "+&Yes\v"
  "+&Ja\v"
  ,
  "-&No\v"
  "-&Nein\v"
  ,
  "&No\v"
  "&Nein\v"
  ,
  "Name already defined!\v"
  "Name ist bereits definiert!\v"
  ,
  " Header\v"
  " Spaltenüberschrift\v"
  ,
  "&Name:\v"
  "&Name:\v"
  ,
  "+OK\v"
  "+OK\v"
  ,
  "Name can't be empty!\v"
  "Name kann nicht leer sein!\v"
  ,
  "-Cancel\v"
  "-Abbrechen\v"
  ,
  "&Headers\v"
  "&Spaltenüberschriften\v"
  ,
  "Bill Of Material - Help\v"
  "Stückliste - Hilfe\v"
  ,
  "Bill Of Material\v"
  "Stückliste\v"
  ,
  "List type\v"
  "Listen-Typ\v"
  ,
  "&Parts\v"
  "&Bauteile\v"
  ,
  "&Values\v"
  "&Werte\v"
  ,
  "Output format\v"
  "Ausgabeformat\v"
  ,
  "CSV separator\v"
  "CSV Trennzeichen\v"
  ,
  "&Text\v"
  "&Text\v"
  ,
  "&CSV\v"
  "&CSV\v"
  ,
  "&HTML\v"
  "&HTML\v"
  ,
  "+Vie&w\v"
  "+&Vorschau\v"
  ,
  "&Save...\v"
  "&Speichern...\v"
  ,
  "H&elp\v"
  "H&ilfe\v"
  };
int Language = strstr (I18N [0], language ()) / 3;




string tr (string s)
{
  string t = lookup (I18N, s, Language, '\v');
  return t ? t : s;
}




if (!schematic)
{
  dlgMessageBox (usage + tr ("<hr><b>ERROR: No schematic!</b><p>\nThis program can only work in the schematic editor."));
  exit (1);
}




int NumParts;

numeric string Lines[];
numeric string PartName [];

// 2012-08-17 cwi: added PartLib []
string  PartValue [], PartDevice [], PartPackage [], PartHeadline [], PartLib [];
numeric string PartDescription [];
int PartValueOn[];
int Selected;

numeric string PartSide [];  // str: CS or SS
real PartInchX [], PartInchY [], PartMmX [], PartMmY [], PartAngle []; // each part's X-Y data




// cwi: Added arrays for an arbitraty number of attributes.
int FoundAttributes = 0;            // # of different attribute names found in schematic.
numeric string AttributesList[];    // Sorted list of all attributes found in the schematic.
numeric string PartAttributes[];    // Adjusted list of attributes per part.




enum { ltParts, ltValues };         // List Types
enum { ofText, ofCSV, ofHTML };     // Output Formats
enum { chColon, chComma };          // CSV charcter
int ListType = 0;
int OutputFormat = 0;
int CSVSeparator = 0;





/*****************************************************************************
	Called from output to CSV format.

	Goes thru given string and changes all double-quotes
		into double-double-quotes, as required by CSV spec.

	Fields that contain double quote characters must be surounded
	by double-quotes, and the embedded double-quotes must each be
	represented by double double-quotes.  The first double-quote
	"escapes" its following double-quote -- a backslash will not work.

	So,   John "Da Man" Doe   must be   "John ""Da Man"" Doe"
		(NOT "John \"Da Man\" Doe")
	
	2013-10-04 creation
*/
string escapeDoubleQuote( string s )
{
	string dq = "\"";
	string esc = "\\";
	string c; // current character being checked in string
	string out;

	int slen = strlen( s );

	for( int i = 0; i < slen; i++ )
	{
		c = strsub( s, i, 1);
		if( c == dq )
		{
			out += dq + dq;
		}
		else
		{
			out += s[i];
		}
	}
	return out;
}




/*****************************************************************************
	Name:		Trim
	Description:	Function to trim non-printable characters from the start and end of a string.
	Called by:	GenerateOutput
			, AddDefaultName
			, EditStructure
			, GetOptions
			, OpenSetup,
			, AddDefaultSetup
	Parameters:	String to process
	Calls:		
	Returns:	Processed string
*/
string Trim(string s)
{
	while (s && isspace(s[0])) s = strsub(s, 1);
	while (s && isspace(s[strlen(s) - 1])) s = strsub(s, 0, strlen(s) - 1);
	return s;
}




/*****************************************************************************
	Name:		TrimSpace
	Description:	Function to trim non-printable characters from the start and end of a
			string.  If the result is an empty string, it returns a single space.
			This is needed because of a bug in Eagle's ULP treatment of empty
			strings.  When alphabetizing, Eagle does not realize that an empty
			string goes before anything else, so it thinks that "a" goes before "".
			This function fixes the problem by turning "" into " ".
	Called by:	GenerateOutput, EditStructure, GetOptions
	Parameters:	String to process
	Calls:		Trim
	Returns:	Processed string
*/
string TrimSpace(string s)
{
	s = Trim(s);
	if (!s) s = " ";
	return s;
}




/*****************************************************************************

*/
string StripWhiteSpace (string s)
{
  while (s && isspace (s [0]))
    s = strsub (s, 1);
  while (s && isspace (s [strlen (s) - 1]))
    s = strsub (s, 0, strlen (s) - 1);
  return s;
}




/*****************************************************************************
	Collect part data from the schematic.

	Arguments:
	
	Returns:	NumParts            - # of found parts
			PartName []
			PartValue []
			PartDevice []
			PartPackage []
			PartHeadline []
			PartDescription []
			PartLib []
			PartValueOn []      - 0=part value off, 1= part value on, 2=override with attr. VAL
			FoundAttributes     - # of different attribute names found in schematic.
			AttributesList []   - Sorted list of all attributes found in the schematic.
			PartAttributes []   - Adjusted list of attributes per part.
			PartSide []	str
			PartInchX []	real
			PartInchY []	real
			PartMmX []	real
			PartMmY []	real
			PartAngle []	real
*/
void CollectPartData (void)
{
  int Found = 0;
  int i;
  string attr [];
	string elemname;
  NumParts = 0;

  // First, collect the names of all available attributes.
  FoundAttributes = 0;
  schematic (SCH)
  {
    SCH.parts (P)
    {
      if (P.device.package)
      {
        P.attributes (A)
        {
          if (0 == FoundAttributes)
          {
            // First one
            AttributesList [0] = A.name;
            FoundAttributes = 1;
          }
          else
          {
            Found = 0;
            for (i = 0; i < FoundAttributes; i ++)
            {
              if (A.name == AttributesList [i])
              {
                // Found an already listed attribute
                Found = 1;
                break;
              }
            }
            if (0 == Found)
            {
              // Attribute not listed, add at the end.
              AttributesList [FoundAttributes] = A.name;
              FoundAttributes ++;
            }
          }
        }
      }
    }
  }
  sort (FoundAttributes, AttributesList);


  // Second, collect all data
  schematic (SCH)
  {
    SCH.parts (P)
    {
      if (P.device.package)
      {
        PartName [NumParts] = P.name;
        PartValue [NumParts] = P.value;
        PartDevice [NumParts] = P.device.name;
        PartPackage [NumParts] = P.device.package.name;
        PartHeadline [NumParts] = P.device.headline;
        PartDescription [NumParts] = P.device.description;
        PartValueOn [NumParts] = P.device.value == "On";
        PartLib [NumParts] = P.device.library;
        // Zero all strings
        for (i = 0; i < FoundAttributes; i ++)
          attr [i] = "";
        P.attributes(A)
        {
          for (i = 0; i < FoundAttributes; i ++)
            if (A.name == AttributesList [i])
            {
              attr [i] = A.value;
              break;
            }
          if ("VAL" == A.name && 0 < strlen (A.value))
          {
            // Override old fashioned value information!
            PartValueOn [NumParts] = 2;
            // 2012-08-17 cwi: "VAL" always overwrites classic "VALUE" entry!
            PartValue [NumParts] = A.value;
          }
        }
        PartAttributes [NumParts] = strjoin (attr, ';');
        NumParts ++;
      }
    }
  }

	// Third, go thru board, grab and store location of each part.
	// If there is a board, scan all its parts, comparing by name to all schematic part names, and assign location data when found.
	if(project.board)
	{
		// Scan the board
		project.board(BRD)
		{
			// Scan elements on the board
			BRD.elements(E)
			{
				// Get element name
				elemname = TrimSpace(E.name);

				// For each board element, scan all schematic parts for match by name:
				for(i = 0; i < NumParts; i++)
				{
					// Find matching name
					if(PartName[i] == elemname)
					{	
						// Default to component side
						PartSide[i] = "CS";
						// Unless on solder side
						if(E.mirror)
						{
							PartSide[i] = "SS";
						}

						// Get the coordinates
						PartInchX[i] = u2inch(E.x);
						PartInchY[i] = u2inch(E.y);
						PartMmX[i] = u2mm(E.x);
						PartMmY[i] = u2mm(E.y);

						PartAngle[i] = E.angle;
					} // find matching name
				} // for i -- scan schematic parts
			} // BRD.elements(E)
  		} // scan board
	} // board exists

}




/*****************************************************************************

*/
void GeneratePartList(void)
{
  int NumLines = 0;
  string attr [], s;

	string tmp_inchx;
	string tmp_inchy;
	string tmp_mmx;
	string tmp_mmy;
	string tmp_angle;

  s = strjoin (AttributesList, '\t');
  Lines [NumLines ++] = tr ("Part\tValue\tDevice\tPackage\tLibrary\tDescription\tSide\tInchX\tInchY\tmmX\tmmY\tAngle\t") + s;
  for (int i = 0; i < NumParts; i ++)
  {
    strsplit (attr, PartAttributes [i], ';');
    s = strjoin (attr, '\t');
	
	sprintf( tmp_inchx, "%10.4f", PartInchX[i] );
	sprintf( tmp_inchy, "%10.4f", PartInchY[i] );
	sprintf( tmp_mmx, "%10.4f", PartMmX[i] );
	sprintf( tmp_mmy, "%10.4f", PartMmY[i] );
	sprintf( tmp_angle, "%7.2f", PartAngle[i] );

    Lines [NumLines] = PartName [i] + "\t"
			+ PartValue [i] + "\t"
			+ PartDevice [i] + "\t"
			+ PartPackage [i] + "\t"
			+ PartLib [i] + "\t"
			+ PartHeadline [i] + "\t"
			+ PartSide [i] + "\t"
			+ tmp_inchx + "\t"
			+ tmp_inchy + "\t"
			+ tmp_mmx + "\t"
			+ tmp_mmy + "\t"
			+ tmp_angle + "\t"
			+ s;
    NumLines ++;
  }
  Lines [NumLines] = "";
}




/*****************************************************************************
	Generate list with one entry per value.
	'VALUE' is replaced by the value of attribute 'VAL', if existing.
*/
void GenerateValueList (void)
{
  int NumLines = 0;
  int Index [];
  int i_val;
  string attr [], s, s_val;

  s = strjoin (AttributesList, '\t');
  // Get index into array.
  for (i_val = 0; i_val < FoundAttributes; i_val ++)
    if ("VAL" == AttributesList [i_val])
      break;

  // 2010-04-17 cwi: Included description.
  Lines [NumLines ++] = tr ("Qty\tValue\tDevice\tParts\tLibrary\tDescription\t") + s;
  sort (NumParts, Index, PartDevice, PartValue, PartAttributes);
  for (int n1 = 0, n2 = 0; ++ n2 <= NumParts; )
  {
    int i1 = Index [n1];
    strsplit (attr, PartAttributes [i1], ';');
    s = strjoin (attr, '\t');
    s_val = attr [i_val];
    if (n2 < NumParts)
    {
      int i2 = Index [n2];
      strsplit (attr, PartAttributes [i2], ';');
      if (PartValue[i1] == PartValue[i2] && PartDevice[i1] == PartDevice[i2] &&
          s_val == attr [i_val] && PartAttributes [i1] == PartAttributes [i2])
        continue;
    }
    string Quantity;
    sprintf (Quantity, "%d", n2 - n1);
    if (2 == PartValueOn [i1])
      Lines [NumLines] = Quantity + "\t" + s_val + "\t" + PartDevice [i1] + "\t";
    else
      Lines [NumLines] = Quantity + "\t" + PartValue [i1] + "\t" + PartDevice [i1] + "\t";
    for (;;)
    {
      Lines [NumLines] += PartName [i1];
      if (++n1 < n2)
      {
        i1 = Index [n1];
        Lines [NumLines] += ", ";
      }
      else
        break;
    }
    // cwi: add extra information from attributes
    // 2010-04-17 cwi: Included library & description.
    Lines [NumLines] += "\t" + PartLib [i1] + "\t" + PartHeadline [i1] + "\t" + s;
    NumLines ++;
  }
  Lines [NumLines] = "";
}




/*****************************************************************************

*/
void GenerateList (void)
{
  switch (ListType)
  {
    case ltParts:  GeneratePartList (); break;
    case ltValues: GenerateValueList (); break;
  }
}




/*****************************************************************************

*/
string MakeListHeader (void)
{
  string s;
  schematic(SCH)
    sprintf (s, tr ("Partlist exported from %s at %s"), SCH.name, t2string (time ()));
  return s;
}




/*****************************************************************************

*/
string MakeListText(void)
{
  int l, Width [];
  string List;
  int numHeaders;

  for (l = 0; Lines [l]; l ++)
  {
    string a [];
    for (int n = strsplit (a, Lines [l], '\t'); n --; )
      Width [n] = max (Width [n], strlen (a [n]));
  }

  List = MakeListHeader () + "\n\n";

  for (l = 0; Lines [l]; l ++)
  {
    string line, a [];

    int n = strsplit (a, Lines [l], '\t');
    if (l == 0)
      numHeaders = n;
    else
      n = numHeaders; // for the hidden key!
    for (int i = 0; i < n; i ++)
    {
      string s;

      sprintf (s, "%s%-*s", line ? " " : "", Width [i], a [i]);
      line += s;
    }
    List += line + "\n";
  }
  return List;
}




/*****************************************************************************
	2013-10-04 Modified  to escapeDoubleQuote() per CSV spec.

	2008-11-24 Christian Schlittler:
	Make comma-separated list, with all values double-quoted.
*/
string MakeListCSV (void)
{
  string List;
  int numHeaders, i, l;

  for (l = 0; Lines [l]; l ++)
  {
    string a [];
    int n = strsplit (a, Lines [l], '\t');

    if (l == 0)
      numHeaders = n;
    else
      n = numHeaders; // for the hidden key!

    // 2012-08-17 cwi: Separate list either with ";" or with ",". Default is ";".
    if (CSVSeparator == 0)
      for (i = 0; i < n; i ++)
        List += "\"" + escapeDoubleQuote( a[i] ) + "\";";
    else
      for (i = 0; i < n; i ++)
        List += "\"" + escapeDoubleQuote( a[i] ) + "\",";

    List += "\n";
  }
  return List;
}




/*****************************************************************************

*/
string MakeListHTML (void)
{
  string List;
  int numHeaders;

  List = "<b>" + MakeListHeader() + "</b>\n<p>\n";
  List += "<table>\n";
  for (int l = 0; Lines[l]; l++)
  {
    List += "<tr>";
    string a [];
    int n = strsplit (a, Lines [l], '\t');
    if (l == 0)
      numHeaders = n;
    else
      n = numHeaders; // for the hidden key!
    for (int i = 0; i < n; i ++)
    {
      if (l == 0)
        a[i] = "<b>" + a[i] + "</b>";
      List += "<td>" + a[i] + "</td>";
    }
    List += "</tr>\n";
  }
  List += "</table>\n";
  return List;
}




/*****************************************************************************

*/
string MakeList (void)
{
  switch (OutputFormat)
  {
    case ofText: return MakeListText(); break;
    case ofCSV:  return MakeListCSV(); break;
    case ofHTML: return MakeListHTML(); break;
  }
  return "";
}




/*****************************************************************************

*/
void ViewList (void)
{
  dlgDialog (tr ("Bill Of Material - Preview"))
  {
    string s = MakeList ();
    if (OutputFormat == ofText || OutputFormat == ofCSV)
      s = "<pre>" + s + "</pre>";
    dlgHBoxLayout dlgSpacing (400);
    dlgHBoxLayout
    {
      dlgVBoxLayout dlgSpacing (300);
      dlgTextView (s);
    }
    dlgHBoxLayout
    {
      dlgStretch (1);
      dlgPushButton (tr ("-Close")) dlgReject ();
    }
  };
}




/*****************************************************************************

*/
void SaveList (void)
{
  // 2008-11-24 cwi:
  // - Added new format extension .csv
  // - Changed from .bom to .txt for text format.
  string FileName;
  string FileExt;

  switch (OutputFormat)
  {
    case ofText: FileExt = ".txt";  break;
    case ofHTML: FileExt = ".html"; break;
    case ofCSV:  FileExt = ".csv";  break;
  }
  schematic(SCH) FileName = filesetext (SCH.name, FileExt);
  FileName = dlgFileSave (tr ("Save Bill Of Material"), FileName);
  if (FileName)
  {
    string a [];
    if (!fileglob (a, FileName) || dlgMessageBox (tr ("File '") + FileName +
        tr ("' exists\n\nOverwrite?"), tr("+&Yes"), tr("-&No")) == 0)
    {
      output (FileName, "wt")
      {
        printf ("%s", MakeList ()); // using "%s" to avoid problems if list contains any '%'
      }
    }
  }
}




/*****************************************************************************

*/
void DisplayHelp (void)
{
  dlgDialog (tr ("Bill Of Material - Help"))
  {
    dlgHBoxLayout dlgSpacing (400);
    dlgHBoxLayout
    {
      dlgVBoxLayout dlgSpacing (300);
      dlgTextView (language () == "de" ? HelpTextDE : HelpTextEN);
    }
    dlgHBoxLayout
    {
      dlgStretch (1);
      dlgPushButton (tr ("-Close"))
      dlgReject ();
    }
  };
}











/*****************************************************************************
	RUN
*/

CollectPartData();
GenerateList();

dlgDialog (tr ("Bill Of Material"))
{
  dlgListView ("", Lines, Selected);
  dlgHBoxLayout
  {
    dlgStretch (1);
    dlgGroup(tr ("List type"))
    {
      dlgRadioButton (tr ("&Parts"), ListType) GeneratePartList ();
      dlgRadioButton (tr ("&Values"), ListType) GenerateValueList ();
    }
    dlgGroup (tr ("Output format"))
    {
      // 2008-10-09: Entries swapped for correct function.
      dlgRadioButton (tr ("&Text"), OutputFormat);
      // 2008-11-24 cwi: New format added.
      dlgRadioButton (tr ("&CSV"), OutputFormat);
      dlgRadioButton (tr ("&HTML"), OutputFormat);
    }
    // 2012-08-17 cwi: Added selector for different types of CSV separator for US or German Excel versions.
    dlgGroup (tr ("CSV separator"))
    {
      dlgRadioButton (";", CSVSeparator);
      dlgRadioButton (",", CSVSeparator);
    }
  }
  dlgHBoxLayout
  {
    dlgStretch (1);
    dlgPushButton (tr ("+Vie&w"))    ViewList ();
    dlgPushButton (tr ("&Save...")) SaveList ();
    dlgPushButton (tr ("H&elp"))    DisplayHelp ();
    dlgPushButton (tr ("-Close"))   dlgAccept ();
  }
};
