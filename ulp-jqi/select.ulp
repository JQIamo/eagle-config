//======================================================
// SELECT v 1.0.0
//
// Eagle v5.7 or later is required. Only the Board editor is supported
//
// Selects components or nets listed at the command line and filter/subtract/add or make new group
// 
// This software is released under the BSD 4-clause license:
//
// Copyright (c) 2010, Damhave Systems
// All rights reserved.

// Redistribution and use in source and binary forms, with or without modification, are permitted provided that the following conditions are met:

//	*	Redistributions of source code must retain the above copyright notice, this list of conditions and the following disclaimer.
//	*	Redistributions in binary form must reproduce the above copyright notice, this list of conditions and the following disclaimer
// 		in the documentation and/or other materials provided with the distribution.
//	*	Neither the name of the Damhave Systems nor the names of its contributors may be used to endorse or promote products derived from
//	    this software without specific prior written permission.
// THIS SOFTWARE IS PROVIDED BY THE COPYRIGHT HOLDERS AND CONTRIBUTORS "AS IS" AND ANY EXPRESS OR IMPLIED WARRANTIES, INCLUDING, BUT NOT LIMITED TO,
// THE IMPLIED WARRANTIES OF MERCHANTABILITY AND FITNESS FOR A PARTICULAR PURPOSE ARE DISCLAIMED. IN NO EVENT SHALL THE COPYRIGHT HOLDER OR CONTRIBUTORS
// BE LIABLE FOR ANY DIRECT, INDIRECT, INCIDENTAL, SPECIAL, EXEMPLARY, OR CONSEQUENTIAL DAMAGES (INCLUDING, BUT NOT LIMITED TO, PROCUREMENT OF SUBSTITUTE
// GOODS OR SERVICES; LOSS OF USE, DATA, OR PROFITS; OR BUSINESS INTERRUPTION) HOWEVER CAUSED AND ON ANY THEORY OF LIABILITY, WHETHER IN CONTRACT,
// STRICT LIABILITY, OR TORT (INCLUDING NEGLIGENCE OR OTHERWISE) ARISING IN ANY WAY OUT OF THE USE OF THIS SOFTWARE, EVEN IF ADVISED OF THE POSSIBILITY
// OF SUCH DAMAGE.
//======================================================
#usage	"<B>Selects components or nets listed at the command line and filter/subtract/add or make new group</B>"
"<P>"
	"Usage:<br>"
	"run select [-flag{flag}] {component}<br><br>"
	"Flags:<br>"
	"a: add to existing group<br>"
	"c: select components<br>"
	"e: use regular expressions (regex) instead of wildcards<br>"
	"f: filter existing group<br>"
	"n: select nets and signals<br>"
	"p: select components with specified packages<br>"	
	"s: subtract from existing group<br>"
	"v: select components with specified values<br>"	
	"The existing group is cleared unless one of the flags -a or -s are used.<br>"
	"The -c flag is default set if no flags are specified<br>"
	"<P>"
	"Example: run select -c R* C*"	
	"<P>"
	"Copyright (c) 2010 Damhave Systems"
	"<P>"
	"<Author>Danny Damhave<br>Damhave Systems<br>www.damhave.com</Author><br><br>"
	"This ulp is released under the BSD 4-clause license. See source code for details!"

	enum {false, true};
int  firstInList = 1, addFlag = 0, subtractFlag = 0, selectComponentsFlag = 1, regexFlag = 0, filterFlag = 0, selectNetsFlag = 0, selectPackagesFlag = 0, selectValuesFlag = 0;

int isMatch(string s, string test, int useRegex)
{	
	string regex = !useRegex ?  "^" : test;
	if (!useRegex)
	{
		for(int i = 0; test[i];)
		{
			switch(test[i])
			{
				case '[': regex += strsub(test, i, strchr(test, ']', i) - i + 1), i += strchr(test, ']', i) - i + 1; break;
				case '?': regex += ".", i++; break;
				case '*': regex += ".*", i++; break;
				case '^': case '$': case '.': case '{': case '}': case '(': case ')':  case '|': case '\\':
				regex += "\\" + test[i], i++; break;
				default: regex += test[i], i++;
			}
		}
		regex +='$';
	}
	return strxstr(s, regex, 0) == 0;
}

int inList(string name)
{
	for(int i = firstInList; i < argc && argv[i] != ""; i++)
	if (regexFlag)
	{
		if (isMatch(name, argv[i], regexFlag)) return true;
	}
	else
	{
		if (isMatch(name, strupr(argv[i]), regexFlag)) return true;		
	}
	return false;
}

int inListCaseSensitive(string name)
{
	for(int i = firstInList; i < argc && argv[i] != ""; i++)
		if (isMatch(name, argv[i], regexFlag)) return true;
	return false;
}

int snapToGrid(UL_BOARD brd, int coordinate)
{
	real gSize;
	if (brd.grid.unitdist == GRID_UNIT_MIC) gSize = brd.grid.distance * 10;
	else if  (brd.grid.unitdist == GRID_UNIT_MM) gSize = brd.grid.distance * 10000;
	else if  (brd.grid.unitdist == GRID_UNIT_MIL) gSize = brd.grid.distance * 254;
	else if  (brd.grid.unitdist == GRID_UNIT_INCH) gSize = brd.grid.distance * 254000;
	return (round (coordinate / gSize) * gSize);	
}

//		***** The ulp begins here *****
if (!board && !dlgMessageBox("Can only be used in board editor.\n")) exit(1);
if (EAGLE_VERSION < 5 || (EAGLE_VERSION == 5 && EAGLE_RELEASE < 7) && !dlgMessageBox("Requires Eagle v5.7 or later.\n")) exit(1);

string dummy[];
if (!fileglob(dummy, path_ulp[0]  + "/"+ "accepted2.txt"))
{
	if (!dlgMessageBox("Please consider to outsource your hardware design reviews and designs to\n\n               Damhave Systems\n\n              www.damhave.com\n\nThis software is released under the 4-clause BSD license. See the source code for details.\n", "I Accept", "Cancel"))
	{
		output(path_ulp[0] + "/"+ "accepted2.txt", "wt") { printf("Accepted\n"); }	
	}
	else exit(0);
}

while (argc>firstInList)
{
	string flags = argv[firstInList];
	if (flags[0] == '-')
	{
		if (strlen(flags) == 1 && !dlgMessageBox("No flags.\n")) exit(1);
		selectComponentsFlag = 0;
		for (int i = 1; flags[i]; i++)
		{
			switch (flags[i])
			{
				case 'a' : addFlag = true; break;
				case 'c' : selectComponentsFlag = true; break;
				case 'e' : regexFlag = true; break;
				case 'f' : filterFlag = true; break;
				case 'n' : selectNetsFlag = true; break;
				case 'p' : selectPackagesFlag = true; break;
				case 's' : subtractFlag = true; break;
				case 'v' : selectValuesFlag = true; break;
				default : dlgMessageBox("No such flag.\n"); exit(1);
			}
		}	 
		firstInList++;
		if ((addFlag && subtractFlag) || (filterFlag && (addFlag || subtractFlag)) || (selectComponentsFlag && selectNetsFlag) && !dlgMessageBox("Illegal flag combination.\n")) exit(1);
	}
	else break;	
}

status("Selecting Objects...");

board(brd) if (!addFlag && !subtractFlag && !filterFlag)
{
	brd.circles(c) clrgroup(c);
	brd.elements(e) clrgroup(e);
	brd.frames(f) clrgroup(f);
	brd.holes(h) clrgroup(h);
	brd.polygons(p) clrgroup(p);
	brd.rectangles(r) clrgroup(r);
	brd.signals(s) clrgroup(s);
	brd.texts(t) clrgroup(t);
}

if (argc>firstInList)
{
	board(brd)
	{
		if (selectComponentsFlag)
		{
			brd.elements(element)
			if (inList(element.name))
			{
				if (filterFlag); else if (addFlag || !subtractFlag) setgroup(element); else if (subtractFlag) clrgroup(element);
			}
			else if (filterFlag) clrgroup(element);
		}
		else if (selectNetsFlag)
		{
			brd.signals(signal)
			if (inList(signal.name))
			{
				if (filterFlag); else if (addFlag || !subtractFlag) setgroup(signal); else if (subtractFlag) clrgroup(signal);
			}
			else if (filterFlag) clrgroup(signal);
			
		}			
		else if (selectPackagesFlag)
		{
			brd.elements(element)
			if (inList(element.package.name))
			{
				if (filterFlag); else if (addFlag || !subtractFlag) setgroup(element); else if (subtractFlag) clrgroup(element);
			}
			else if (filterFlag) clrgroup(element);
		}
		else if (selectValuesFlag)
		{
			brd.elements(element)
			if (inListCaseSensitive(element.value))
			{
				if (filterFlag); else if (addFlag || !subtractFlag) setgroup(element); else if (subtractFlag) clrgroup(element);
			}
			else if (filterFlag) clrgroup(element);
		}
	}
}
exit("WINDOW;");
