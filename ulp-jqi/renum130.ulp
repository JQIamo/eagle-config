/*--------------------------------------------------------------------------------------------

   Renumbering of components (Version 1.30)

   Filename: renum130.ulp
   Written by: Michel Dagenais <jcmae@sympatico.ca>
   Date: October 7th 1998

	1. This ULP will renumber a board starting from any corner, renaming from 1, either horizontally, vertically or based on pcb aspect ratio.

	2. You have a user-defined window to determine row or column width for components scanning.

	3. Plus, it does the component side THEN the solder side continuing in sequence or starting with new suffixes.

	4. In all cases, it generates two files:
		'{day}{hour}{minute}{second}preview.scr' for preview and
		'{day}{hour}{minute}{second}renum.scr' for renumbering.

		For instance, executing this ULP on October 7th 1998 at 10:36:00 AM would generate two files:
		'07103600preview.scr' and
		'07103600renum.scr'.

		The reason for that particular naming is to avoid overwriting satisfaying script file when accidentally executing this ULP.

	5. Your board MUST be drawn on layer 20 (Dimension) and all components MUST be inside it otherwise the result is unpredictable.

--------------------------------------------------------------------------------------------*/
//		You can change the following parameters:
//
real pcb_ratio = 2 ;				// 1:automatic (pcb_length/pcb_height), <1:horizontally, >1:vertically
real window = 0.4 ;				// default window width
int sequence_bottom = 100	 ;	// If no overlap, use this new suffix to start on BOTTOM. Otherwise continue in sequence.
string corner_top = "TL" ;		// TL:Top-Left, BL: Bottom-Left, BR: Bottom-Right, TR:Top-Right. (default is TL on top)
string corner_bottom = "TR" ;	// TL:Top-Left, BL: Bottom-Left, BR: Bottom-Right, TR:Top-Right. (default is TR on  bottom)
//
/*------------------------------------------------------------------------------------------*/
//
int tmp_int, i, j, z, length_of_name, c_top, c_bottom, number_prefix, largest_number_prefix;
int i_p_top, index_top[], old_suffix_top[], new_suffix_top[];
real comp_x_abs_top[], comp_y_abs_top[];
int i_p_bottom, index_bottom[], old_suffix_bottom[], new_suffix_bottom[];
real comp_x_abs_bottom[], comp_y_abs_bottom[];
int i_p_both, index_both[], old_suffix_both[], new_suffix_both[];
real tmp_real, w, pcb_min_x, pcb_min_y, pcb_max_x, pcb_max_y, pcb_length, pcb_height;
string tmp_string, ref_name, last_prefix, prefix_top[], prefix_bottom[], prefix_both[];
//
z = time();
board(B)
{
	// Get board size to determine ratio.
	tmp_int = 1;
	B.wires(W)
	{
		if (W.layer == 20)
		{
			if (tmp_int == 1)
			{
			pcb_min_x = u2inch(W.x1);
			pcb_min_y = u2inch(W.y1);
			pcb_max_x = u2inch(W.x1);
			pcb_max_y = u2inch(W.y1);
			tmp_int = 0;
			}
			if (u2inch(W.x1) < pcb_min_x){pcb_min_x = u2inch(W.x1);}
			if (u2inch(W.x1) > pcb_max_x){pcb_max_x = u2inch(W.x1);}
			if (u2inch(W.x2) < pcb_min_x){pcb_min_x = u2inch(W.x2);}
			if (u2inch(W.x2) > pcb_max_x){pcb_max_x = u2inch(W.x2);}
			if (u2inch(W.y1) < pcb_min_y){pcb_min_y = u2inch(W.y1);}
			if (u2inch(W.y1) > pcb_max_y){pcb_max_y = u2inch(W.y1);}
			if (u2inch(W.y2) < pcb_min_y){pcb_min_y = u2inch(W.y2);}
			if (u2inch(W.y2) > pcb_max_y){pcb_max_y = u2inch(W.y2);}
		}
	}
	pcb_length = pcb_max_x - pcb_min_x;
	pcb_height = pcb_max_y - pcb_min_y;
	if (pcb_ratio == 1)
	{
		pcb_ratio = pcb_length/pcb_height;
	}
	if (strupr(corner_top) == "TR") {c_top = 1 ;}
	if (strupr(corner_top) == "TL") {c_top = 2 ;}
	if (strupr(corner_top) == "BL") {c_top = 3 ;}
	if (strupr(corner_top) == "BR") {c_top = 4 ;}
	number_prefix = 1;
	last_prefix = "";
	largest_number_prefix = 1;
	B.elements(E)
	{
		ref_name = E.name ;
		length_of_name = strlen(ref_name) ;
		prefix_top[i_p_top] = "" ;
		new_suffix_top[i_p_top] = 0 ;
		tmp_string = "" ;
		if (isdigit(ref_name[length_of_name - 1]) && E.mirror == 0 )
		{
			for (i = 0; !isdigit(ref_name[i]); ++i)
			{
				prefix_top[i_p_top] = prefix_top[i_p_top] + ref_name[i] ;
			}
			if (prefix_top[i_p_top] == last_prefix) {++number_prefix;}
			else
			{
				last_prefix = prefix_top[i_p_top];
				if (number_prefix > largest_number_prefix)
				{
				largest_number_prefix = number_prefix;
				number_prefix = 1;
				}
			}
			for (i = 0; i < length_of_name; ++i)
			{
				if (isdigit(ref_name[i]))
				{
					tmp_string = tmp_string + ref_name[i] ;
				}
			}
			old_suffix_top[i_p_top] = strtol(tmp_string) ;
			switch (c_top)
			{
			case 1:		// Top-Right
				{
				comp_x_abs_top[i_p_top] = abs(u2inch(E.x) - pcb_max_x) ;
				comp_y_abs_top[i_p_top] = abs(u2inch(E.y) - pcb_max_y) ;
				break;
				}
			case 2:		// Top-Left
				{
				comp_x_abs_top[i_p_top] = abs(u2inch(E.x) + abs(pcb_min_x)) ;
				comp_y_abs_top[i_p_top] = abs(u2inch(E.y) - pcb_max_y) ;
				break;
				}
			case 3:		// Bottom-Left
				{
				comp_x_abs_top[i_p_top] = abs(u2inch(E.x) + abs(pcb_min_x)) ;
				comp_y_abs_top[i_p_top] = abs(u2inch(E.y) + abs(pcb_min_y)) ;
				break;
				}
			case 4:		// Bottom-Right
				{
				comp_x_abs_top[i_p_top] = abs(u2inch(E.x) - pcb_max_x) ;
				comp_y_abs_top[i_p_top] = abs(u2inch(E.y) + abs(pcb_min_y)) ;
				break;
				}
			default:		// default is Top-Left Corner for Top side.
				{
				comp_x_abs_top[i_p_top] = abs(u2inch(E.x) + abs(pcb_min_x)) ;
				comp_y_abs_top[i_p_top] = abs(u2inch(E.y) - pcb_max_y) ;
				}
			}
			++i_p_top ;
		}
	}
}
if (pcb_ratio >= 1)
{
	sort (i_p_top, index_top, comp_x_abs_top, comp_y_abs_top, prefix_top, old_suffix_top, new_suffix_top) ;
	j = 0 ;
	do
	{
		w = comp_x_abs_top[index_top[j]] + window;
		for (i = j + 1; i < i_p_top; ++i)
		{
			if (comp_x_abs_top[index_top[i]] > w)
			{
				break ;
			}
			if (comp_y_abs_top[index_top[i]] < comp_y_abs_top[index_top[i - 1]])
			{
				tmp_real = comp_x_abs_top[index_top[i - 1]];
				comp_x_abs_top[index_top[i - 1]] = comp_x_abs_top[index_top[i]];
				comp_x_abs_top[index_top[i]] = tmp_real;
				tmp_real = comp_y_abs_top[index_top[i - 1]];
				comp_y_abs_top[index_top[i - 1]] = comp_y_abs_top[index_top[i]];
				comp_y_abs_top[index_top[i]] = tmp_real;
				tmp_string = prefix_top[index_top[i - 1]];
				prefix_top[index_top[i - 1]] = prefix_top[index_top[i]];
				prefix_top[index_top[i]] = tmp_string;
				tmp_int = old_suffix_top[index_top[i - 1]];
				old_suffix_top[index_top[i - 1]] = old_suffix_top[index_top[i]];
				old_suffix_top[index_top[i]] = tmp_int;
				tmp_int = new_suffix_top[index_top[i - 1]];
				new_suffix_top[index_top[i - 1]] = new_suffix_top[index_top[i]];
				new_suffix_top[index_top[i]] = tmp_int;
				i = j ;
			}
		}
		j = i ;
	} while (j < i_p_top) ;
}
else
{
	sort (i_p_top, index_top, comp_y_abs_top, comp_x_abs_top, prefix_top, old_suffix_top, new_suffix_top) ;
	j = 0 ;
	do
	{
		w = comp_y_abs_top[index_top[j]] + window;
		for (i = j + 1; i < i_p_top; ++i)
		{
			if (comp_y_abs_top[index_top[i]] > w)
			{
				break ;
			}
			if (comp_x_abs_top[index_top[i]] < comp_x_abs_top[index_top[i - 1]])
			{
				tmp_real = comp_x_abs_top[index_top[i - 1]];
				comp_x_abs_top[index_top[i - 1]] = comp_x_abs_top[index_top[i]];
				comp_x_abs_top[index_top[i]] = tmp_real;
				tmp_real = comp_y_abs_top[index_top[i - 1]];
				comp_y_abs_top[index_top[i - 1]] = comp_y_abs_top[index_top[i]];
				comp_y_abs_top[index_top[i]] = tmp_real;
				tmp_string = prefix_top[index_top[i - 1]];
				prefix_top[index_top[i - 1]] = prefix_top[index_top[i]];
				prefix_top[index_top[i]] = tmp_string;
				tmp_int = old_suffix_top[index_top[i - 1]];
				old_suffix_top[index_top[i - 1]] = old_suffix_top[index_top[i]];
				old_suffix_top[index_top[i]] = tmp_int;
				tmp_int = new_suffix_top[index_top[i - 1]];
				new_suffix_top[index_top[i - 1]] = new_suffix_top[index_top[i]];
				new_suffix_top[index_top[i]] = tmp_int;
				i = j ;
			}
		}
		j = i ;
	} while (j < i_p_top) ;
}
// Bottom side of board
board(B)
{
	if (strupr(corner_bottom) == "TR") {c_bottom = 1 ;}
	if (strupr(corner_bottom) == "TL") {c_bottom = 2 ;}
	if (strupr(corner_bottom) == "BL") {c_bottom = 3 ;}
	if (strupr(corner_bottom) == "BR") {c_bottom = 4 ;}
	B.elements(E)
	{
		ref_name = E.name ;
		length_of_name = strlen(ref_name) ;
		prefix_bottom[i_p_bottom] = "" ;
		new_suffix_bottom[i_p_bottom] = 0 ;
		tmp_string = "" ;
		if (isdigit(ref_name[length_of_name - 1]) && E.mirror == 1 )
		{
			for (i = 0; !isdigit(ref_name[i]); ++i)
			{
				prefix_bottom[i_p_bottom] = prefix_bottom[i_p_bottom] + ref_name[i] ;
			}
			for (i = 0; i < length_of_name; ++i)
			{
				if (isdigit(ref_name[i]))
				{
					tmp_string = tmp_string + ref_name[i] ;
				}
			}
			old_suffix_bottom[i_p_bottom] = strtol(tmp_string) ;
			switch (c_bottom)
			{
			case 1:		// Top-Right
				{
				comp_x_abs_bottom[i_p_bottom] = abs(u2inch(E.x) - pcb_max_x) ;
				comp_y_abs_bottom[i_p_bottom] = abs(u2inch(E.y) - pcb_max_y) ;
				break;
				}
			case 2:		// Top-Left
				{
				comp_x_abs_bottom[i_p_bottom] = abs(u2inch(E.x) + abs(pcb_min_x)) ;
				comp_y_abs_bottom[i_p_bottom] = abs(u2inch(E.y) - pcb_max_y) ;
				break;
				}
			case 3:		// Bottom-Left
				{
				comp_x_abs_bottom[i_p_bottom] = abs(u2inch(E.x) + abs(pcb_min_x)) ;
				comp_y_abs_bottom[i_p_bottom] = abs(u2inch(E.y) + abs(pcb_min_y)) ;
				break;
				}
			case 4:		// Bottom-Right
				{
				comp_x_abs_bottom[i_p_bottom] = abs(u2inch(E.x) - pcb_max_x) ;
				comp_y_abs_bottom[i_p_bottom] = abs(u2inch(E.y) + abs(pcb_min_y)) ;
				break;
				}
			default:		// default is Top-Right Corner for Bottom side.
				{
				comp_x_abs_bottom[i_p_bottom] = abs(u2inch(E.x) - pcb_max_x) ;
				comp_y_abs_bottom[i_p_bottom] = abs(u2inch(E.y) - pcb_max_y) ;
				}
			}
			++i_p_bottom ;
		}
	}
}
if (pcb_ratio >= 1)
{
	sort (i_p_bottom, index_bottom, comp_x_abs_bottom, comp_y_abs_bottom, prefix_bottom, old_suffix_bottom, new_suffix_bottom) ;
	j = 0 ;
	do
	{
		w = comp_x_abs_bottom[index_bottom[j]] + window;
		for (i = j + 1; i < i_p_bottom; ++i)
		{
			if (comp_x_abs_bottom[index_bottom[i]] > w)
			{
				break ;
			}
			if (comp_y_abs_bottom[index_bottom[i]] < comp_y_abs_bottom[index_bottom[i - 1]])
			{
				tmp_real = comp_x_abs_bottom[index_bottom[i - 1]];
				comp_x_abs_bottom[index_bottom[i - 1]] = comp_x_abs_bottom[index_bottom[i]];
				comp_x_abs_bottom[index_bottom[i]] = tmp_real;
				tmp_real = comp_y_abs_bottom[index_bottom[i - 1]];
				comp_y_abs_bottom[index_bottom[i - 1]] = comp_y_abs_bottom[index_bottom[i]];
				comp_y_abs_bottom[index_bottom[i]] = tmp_real;
				tmp_string = prefix_bottom[index_bottom[i - 1]];
				prefix_bottom[index_bottom[i - 1]] = prefix_bottom[index_bottom[i]];
				prefix_bottom[index_bottom[i]] = tmp_string;
				tmp_int = old_suffix_bottom[index_bottom[i - 1]];
				old_suffix_bottom[index_bottom[i - 1]] = old_suffix_bottom[index_bottom[i]];
				old_suffix_bottom[index_bottom[i]] = tmp_int;
				tmp_int = new_suffix_bottom[index_bottom[i - 1]];
				new_suffix_bottom[index_bottom[i - 1]] = new_suffix_bottom[index_bottom[i]];
				new_suffix_bottom[index_bottom[i]] = tmp_int;
				i = j ;
			}
		}
		j = i ;
	} while (j < i_p_bottom) ;
}
else
{
	sort (i_p_bottom, index_bottom, comp_y_abs_bottom, comp_x_abs_bottom, prefix_bottom, old_suffix_bottom, new_suffix_bottom) ;
	j = 0 ;
	do
	{
		w = comp_y_abs_bottom[index_bottom[j]] + window;
		for (i = j + 1; i < i_p_bottom; ++i)
		{
			if (comp_y_abs_bottom[index_bottom[i]] > w)
			{
				break ;
			}
			if (comp_x_abs_bottom[index_bottom[i]] < comp_x_abs_bottom[index_bottom[i - 1]])
			{
				tmp_real = comp_x_abs_bottom[index_bottom[i - 1]];
				comp_x_abs_bottom[index_bottom[i - 1]] = comp_x_abs_bottom[index_bottom[i]];
				comp_x_abs_bottom[index_bottom[i]] = tmp_real;
				tmp_real = comp_y_abs_bottom[index_bottom[i - 1]];
				comp_y_abs_bottom[index_bottom[i - 1]] = comp_y_abs_bottom[index_bottom[i]];
				comp_y_abs_bottom[index_bottom[i]] = tmp_real;
				tmp_string = prefix_bottom[index_bottom[i - 1]];
				prefix_bottom[index_bottom[i - 1]] = prefix_bottom[index_bottom[i]];
				prefix_bottom[index_bottom[i]] = tmp_string;
				tmp_int = old_suffix_bottom[index_bottom[i - 1]];
				old_suffix_bottom[index_bottom[i - 1]] = old_suffix_bottom[index_bottom[i]];
				old_suffix_bottom[index_bottom[i]] = tmp_int;
				tmp_int = new_suffix_bottom[index_bottom[i - 1]];
				new_suffix_bottom[index_bottom[i - 1]] = new_suffix_bottom[index_bottom[i]];
				new_suffix_bottom[index_bottom[i]] = tmp_int;
				i = j ;
			}
		}
		j = i ;
	} while (j < i_p_bottom) ;
}
i_p_both = 0;
for (i = 0; i < i_p_top; ++i)
{
	prefix_both[i_p_both] = prefix_top[index_top[i]];
	old_suffix_both[i_p_both] = old_suffix_top[index_top[i]];
	new_suffix_both[i_p_both] = new_suffix_top[index_top[i]];
	++i_p_both;
}
for (i = 0; i < i_p_bottom; ++i)
{
	prefix_both[i_p_both] = prefix_bottom[index_bottom[i]];
	old_suffix_both[i_p_both] = old_suffix_bottom[index_bottom[i]];
	new_suffix_both[i_p_both] = new_suffix_bottom[index_bottom[i]];
	++i_p_both;
}
sprintf(tmp_string, "%02d%02d%02d%02dpreview.scr", t2day(z), t2hour(z), t2minute(z), t2second(z));
output(tmp_string, "wt")
{
	printf(";\n");
	printf("Grid Inch;\n");
	printf("Display None;\n");
	printf("Window (%.6f %.6f) (%.6f %.6f);\n", pcb_min_x, pcb_min_y, pcb_max_x, pcb_max_y);
	printf("Display 20 21 22 25 26;\n");
	for (i = 0; i < i_p_both; ++i)
	{
		printf("Show %s%d %s%d;\n", prefix_both[i], old_suffix_both[i], prefix_both[i], old_suffix_both[i]);
	}
}
sprintf(tmp_string, "%02d%02d%02d%02drenum.scr", t2day(z), t2hour(z), t2minute(z), t2second(z));
output(tmp_string,"wt")
{
	printf(";\n");
	printf("Grid Inch;\n");
	printf("Display None;\n");
	printf("Window (%.6f %.6f) (%.6f %.6f);\n", pcb_min_x, pcb_min_y, pcb_max_x, pcb_max_y);
	printf("Display 20 21 22 25 26;\n");
	for (i = 0; i < i_p_both; ++i)
	{
		new_suffix_both[i] = i + 1 ;
	}
	sort (i_p_both, index_both, prefix_both, new_suffix_both, old_suffix_both);
	for (j = 0; j < i_p_both; ++j)
	{
		z = 1;
		tmp_int = 1;
		tmp_string = prefix_both[index_both[j]];
		for (i = j; prefix_both[index_both[i]] == tmp_string; ++i)
		{
			if ((sequence_bottom > largest_number_prefix) && (new_suffix_both[index_both[i]] > i_p_top) && (tmp_int == 1))
			{
				z = sequence_bottom;
				tmp_int = 0;
			}
			if ((new_suffix_both[index_both[i]] > 0) && (old_suffix_both[index_both[i]] != z))
			{
				new_suffix_both[index_both[i]] = z * -1;
			}
			else
			{
				new_suffix_both[index_both[i]] = 0 ;
			}
			++z;
		}
		j = i - 1;
	}
	for (i = 0; i < i_p_both; ++i)
	{
		if (new_suffix_both[index_both[i]] < 0)
		{
			printf("Name '%s%d' '$%s%d';\n", prefix_both[index_both[i]], old_suffix_both[index_both[i]], prefix_both[index_both[i]], abs(new_suffix_both[index_both[i]]));
		}
	}
	for (i = 0; i < i_p_both; ++i)
	{
		if (new_suffix_both[index_both[i]] < 0)
		{
			printf("Name '$%s%d' '%s%d';\n", prefix_both[index_both[i]], abs(new_suffix_both[index_both[i]]), prefix_both[index_both[i]], abs(new_suffix_both[index_both[i]]));
		}
	}
	printf("Grid Last;\n");
}
